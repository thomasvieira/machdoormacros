import FreeCAD
#import JobCmd

Gui.activateWorkbench("CAMWorkbench")
obj = App.ActiveDocument.getObject('Body')
Gui.Selection.addSelection(obj)
Gui.runCommand('Std_Copy',0)
Gui.Selection.clearSelection()
Gui.runCommand('Std_Paste',0)
Gui.Selection.clearSelection()
Gui.runCommand('Std_Paste',0)
Gui.Selection.clearSelection()
myObject = App.ActiveDocument.getObject('Body')
myObject1 = App.ActiveDocument.getObject('Body001')
myObject2 = App.ActiveDocument.getObject('Body002')
myObject1.Placement = App.Placement(App.Vector(0,0,0), App.Rotation(0,-90,0), App.Vector(0,0,0))
myObject2.Placement = App.Placement(App.Vector(0,0,0), App.Rotation(0,90,0), App.Vector(0,0,0))
