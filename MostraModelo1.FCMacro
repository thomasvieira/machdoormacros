# -*- coding: utf-8 -*-

# Macro Begin: C:\Users\thoma\AppData\Roaming\FreeCAD\Macro\EscondeModelos.FCMacro +++++++++++++++++++++++++++++++++++++++++++++++++
import FreeCAD

Gui.Selection.clearSelection()
App.ActiveDocument.getObject("Job").Label = "Usinagens Face Superior"
App.ActiveDocument.getObject("Job").Visibility = True
App.ActiveDocument.getObject("Operations").Visibility = True
App.ActiveDocument.getObject("Stock001").Visibility = True
App.ActiveDocument.getObject("Model").Visibility = True
App.ActiveDocument.getObject("Job001").Visibility = False
App.ActiveDocument.getObject("Operations001").Visibility = False
App.ActiveDocument.getObject("Stock002").Visibility = False
App.ActiveDocument.getObject("Model001").Visibility = False
App.ActiveDocument.getObject("Job002").Visibility = False
App.ActiveDocument.getObject("Operations002").Visibility = False
App.ActiveDocument.getObject("Stock003").Visibility = False
App.ActiveDocument.getObject("Model002").Visibility = False
Gui.Selection.clearSelection()
# Macro End: C:\Users\thoma\AppData\Roaming\FreeCAD\Macro\EscondeModelos.FCMacro +++++++++++++++++++++++++++++++++++++++++++++++++
